FME workspace cw_10.fmw
Shutdown Python:
      import fme
      import smtplib
      from email.mime.text import MIMEText
      from email.mime.multipart import MIMEMultipart
      from datetime import datetime

      dzisiaj = datetime.now().strftime("%d.%m.%Y")
      godzina = datetime.now().strftime("%H:%M:%S")
      subject = "FME_info_zwrotne"
      sender = "$(email)"
      recipients = "$(emailklienta)"
      body = 'Drogi użytkowniku ' + recipients + ', dnia ' + dzisiaj + ' o godzinie ' + godzina + ' pomyślnie zakończono przetwarzanie danych dla powiatu ' + FME_MacroValues['powiat'] + '.'
      password = "$(Haslo)"
      def send_email(subject, body, sender, recipients, password):
          msg = MIMEText(body)
          msg['Subject'] = subject
          msg['From'] = sender
          msg['To'] = recipients

          with smtplib.SMTP_SSL('smtp.gmail.com', 465) as smtp_server:
              smtp_server.login(sender, password)
              smtp_server.sendmail(sender, recipients, msg.as_string())
          print("Message sent!")

      send_email(subject, body, sender, recipients, password)

Parameters:
- email = jakubsumara.js@gmail.com   # Adres e-mail
- pipline = kielce5   # Nazwa Pipline
- Haslo =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   # Wprowadz haslo
- emailklienta = jakubsumara.js@gmail.com   # Adres e-mail klienta
- chmury = 50   # Maksymalne pokrycie chmur
- startdata = 20230701000000   # Data poczatkowa
- data_koniec = 20230731000000   # Data koncowa
- powiat = Kielce   # Nazwa Powiatu
- klucz = d02c5fd7-9855-4dbb-be97-640025da49ac   # Api key
- SourceDataset_SHAPEFILE = $(FME_MF_DIR)powiaty (2)\powiaty.shp   # Source Esri Shapefile(s)
- DestDataset_GEOTIFF = E:\STUDIA\semestr5\BazyDanychPrzestrzennych\cw10   # Destination GeoTIFF Folder

Readers:
- SHAPEFILE_1: SHAPEFILE from $(SourceDataset_SHAPEFILE)

Writers:
- GEOTIFF_1: GEOTIFF to $(DestDataset_GEOTIFF)

powiaty (reader SHAPEFILE_1)
    attributes: gml_id varchar(254), JPT_SJR_KO varchar(254), JPT_POWIER varchar(254), JPT_KOD_JE varchar(254), JPT_NAZWA_ varchar(254), JPT_ORGAN_ varchar(254), JPT_JOR_ID varchar(254), WERSJA_OD varchar(254), WERSJA_DO varchar(254), WAZNY_OD varchar(254), WAZNY_DO varchar(254), JPT_KOD__1 varchar(254), JPT_NAZWA1 varchar(254), JPT_ORGAN1 varchar(254), JPT_WAZNA_ varchar(254), ID_BUFORA_ varchar(254), ID_BUFORA1 varchar(254), ID_TECHNIC varchar(254), IIP_PRZEST varchar(254), IIP_IDENTY varchar(254), IIP_WERSJA varchar(254), JPT_KJ_IIP varchar(254), JPT_KJ_I_1 varchar(254), JPT_KJ_I_2 varchar(254), JPT_OPIS varchar(254), JPT_SPS_KO varchar(254), ID_BUFOR_1 varchar(254), JPT_ID varchar(254), JPT_POWI_1 varchar(254), JPT_KJ_I_3 varchar(254),
      JPT_GEOMET varchar(254), JPT_GEOM_1 varchar(254), SHAPE_LENG varchar(254), SHAPE_AREA varchar(254), REGON varchar(254), RODZAJ varchar(254)
    -> TestFilter_2
TestFilter_2
    DEFAULT_VALUE = <UNFILTERED>
    PASSED_TEST_GROUP_OUTPUT = FIRST
    TEST_LIST = "BOOL_OP,OR,COMPOSITE_TEST,""""""1"""""",TEST_CLAUSE,TEST @Value(JPT_NAZWA_) = powiat $(powiat)",@Value(JPT_NAZWA_) = powiat __powiat_
    @Value(JPT_NAZWA_) = powiat __powiat_ -> Inspector_2
    @Value(JPT_NAZWA_) = powiat __powiat_ -> Reprojector
Inspector_2
Reprojector
    DEST = EPSG:4326
    INTERPOLATION_TYPE_NAME = Nearest Neighbor
    RASTER_CELL_SIZE = Preserve Cells
    RASTER_TOLERANCE = 0.0
    REPROJECTED -> BoundingBoxAccumulator_2
    REPROJECTED -> Clipper [CLIPPER]
BoundingBoxAccumulator_2
    ACCUM_ATTRS_NAME = Use Attributes From One Feature
    BOUNDING_BOX -> EarthCacheConnector
EarthCacheConnector
    api_key = $(klucz)
    end_date = $(data_koniec)
    interval = 7
    min_aoi_coverage_percentage = $(chmury)
    output_id = rgbn-a3e8-11e7-9793-ae4260ee3b4b
    pipeline_name = $(pipline)
    start_date = $(startdata)
    -> Inspector
    -> Sampler
    <Rejected> -> Terminator
Inspector
Sampler
    RATE = 1
    SAMPLE_MODE = No
    SAMPLE_TYPE_LONG = First N Features
    SAMPLED -> RasterBandSeparator
RasterBandSeparator
    BAND_INDEX_FIELD = _band_index
    PALETTE_INDEX_FIELD = _palette_index
    RASTER_INDEX_FIELD = _raster_index
    SPLIT_BY_NAME = Band and Palette
    -> TestFilter
    -> TestFilter_3
TestFilter
    DEFAULT_VALUE = <UNFILTERED>
    PASSED_TEST_GROUP_OUTPUT = FIRST
    TEST_LIST = "BOOL_OP,OR,COMPOSITE_TEST,""""""1"""""",TEST_CLAUSE,TEST @Value(_band_index) = 0",@Value(_band_index) = 0
    @Value(_band_index) = 0 -> NDVICalculator [Red]
TestFilter_3
    DEFAULT_VALUE = <UNFILTERED>
    PASSED_TEST_GROUP_OUTPUT = FIRST
    TEST_LIST = "BOOL_OP,OR,COMPOSITE_TEST,""""""1"""""",TEST_CLAUSE,TEST @Value(_band_index) = 3",@Value(_band_index) = 3
    @Value(_band_index) = 3 -> NDVICalculator [Infrared]
NDVICalculator
    COLORIZE = Blue-Yellow-Green Palette
    INDEXTYPE = NDVI
    SAVIADJUSTMENT = 0.5
    -> Clipper [CANDIDATE]
Clipper
    ADD_NODATA = YES
    BOUNDARY_CASES = INSIDE
    CLEANING_TOLERANCE = Automatic
    CLIPPED_ATTR = _clipped
    CLIPPERS_FIRST = NO
    GENERATE_LIST = NO
    INVALID_PARTS_HANDLING = REJECT_WHOLE
    MISSING_M_MODE = Linear Interpolation
    MISSING_Z_MODE = Planar Interpolation
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    INSIDE -> RasterStatisticsCalculator
    INSIDE -> powiaty_wynik (writer GEOTIFF_1)
powiaty_wynik (writer GEOTIFF_1)
    attributes: gml_id char(254), JPT_SJR_KO char(254), JPT_POWIER char(254), JPT_KOD_JE char(254), JPT_NAZWA_ char(254), JPT_ORGAN_ char(254), JPT_JOR_ID char(254), WERSJA_OD char(254), WERSJA_DO char(254), WAZNY_OD char(254), WAZNY_DO char(254), JPT_KOD__1 char(254), JPT_NAZWA1 char(254), JPT_ORGAN1 char(254), JPT_WAZNA_ char(254), ID_BUFORA_ char(254), ID_BUFORA1 char(254), ID_TECHNIC char(254), IIP_PRZEST char(254), IIP_IDENTY char(254), IIP_WERSJA char(254), JPT_KJ_IIP char(254), JPT_KJ_I_1 char(254), JPT_KJ_I_2 char(254), JPT_OPIS char(254), JPT_SPS_KO char(254), ID_BUFOR_1 char(254), JPT_ID char(254), JPT_POWI_1 char(254), JPT_KJ_I_3 char(254),
      JPT_GEOMET char(254), JPT_GEOM_1 char(254), SHAPE_LENG char(254), SHAPE_AREA char(254), REGON char(254), RODZAJ char(254)
RasterStatisticsCalculator
    RASTER_LEVEL = BAND_ONLY
    RASTER_STATS = "0   MEAN   STDEV   "
Terminator
    MESSAGE = Translation Terminated

FME custom transformer NDVICalculator
This transformer creates NDVI (Normalized Difference Vegetation Index) or SAVI (Soil-Adjusted Vegetation Index) rasters.
Typical Uses
To assess the degree of vegetation and vegetation growth over an area
How Does it Work?
Live plants consume solar radiation in the visible part of the spectrum for synthesis of the organic molecules (predominantly red and blue wavelengths). This is why we see most plants in green, which is reflected more than red and blue. 
Longer-wave (infrared) radiation is not strong enough for photosynthesis, which is why plants very effectively reflect such waves. 
Indices are based on the principle that a large contrast between visible and infrared radiation indicates vegetation growth. Other natural objects (for example, stone, sand, and snow) don't display such a stark contrast between consuming/reflecting red and infrared radiation.
By its nature, NDVI always ranges from -1 to 1, so the transformer creates a numeric Real64 raster, which also can be colored for visualization purposes - in this case, the raster has UINT8 interpretation with RGB24 palette attached. Higher pixel values indicate healthier vegetation.
For more information see:
NDVI
SAVI
Input
The input ports are Red and Infrared ports.
The transformer expects two single band rasters representing red and infrared wave lengths. They can have any unsigned integer interpretation (such us RED, or GRAY, or UINT, etc, 8 or 16 bit). 
To split multiband rasters (for example, near infrared false colors raster NirRG), use the RasterBandSeparator transformer prior to the NDVICalculator. To set proper interpretation, use the RasterBandInterpretationCoercer. 
Output
Depending on coloring options, the transformer outputs a Real64 raster with values ranging from -1 to 1 (this is the original index file), or, for visualization purposes, a UINT8 numeric raster with an RGB24 color palette attached.
Invalid features leave the transformer through the  port. Invalid features include non-raster features as well as multiband rasters and rasters with wrong interpretations.
Parameters
Group By: Mutliple pairs of rasters must have a unqiue ID identifying each pair with the same value.
Index Type: Choose between NDVI and SAVI.
SAVI Canopy Background Adjustment Factor: A multiplier for SAVI. 0.5 is the recommended value.
Colorize: Defines whether the output should be colored. 
The transformer contains two coloring palettes. These palette are stored within the NDVICalculator in AttributeCreator transformers. The palettes can be modified by adjusting the RGB values within the _palette attribute. New palettes can also be added. Make sure that the number of palette entries matches the number of conditions in the RasterExpressionEvaluators that create the indexed rasters - see the comments inside the transformer.

Parameters:
- INDEXTYPE = NDVI   # Index type
- SAVIADJUSTMENT = 0.5   # Canopy Background Adjustment Factor (SAVI only)
- COLORIZE =   # "No Colorization"%"Blue-Yellow-Green Palette"%"Red-Yellow-Blue-Green Palette" Colorize output
- GROUP_BY =   # " " Group By

Red (input)
    -> AttributeCreator_4
Infrared (input)
    -> AttributeCreator_5

Bookmark: Add band id
Note: Band ID allows performing the following operations in a single chain of transformer and then the following splitting by ID for further processing
AttributeCreator_4
    ATTR_TABLE = SET_TO _band_type = red
    -> GeometryFilter
AttributeCreator_5
    ATTR_TABLE = SET_TO _band_type = infrared
    -> GeometryFilter

Bookmark: Check whether features are raster
Note: Non-raster features are not supported.
GeometryFilter
    BREAK_AGG = No
    GEOM_PORT_NAMES = Raster
    RASTER -> RasterPropertyExtractor
    <UNFILTERED> -> Junction_4
Note: Bad Geometry Error
Junction_4
    -> Junction_5

Bookmark: Check whether rasters have a single band
Note: Multiband features are not supported.
RasterPropertyExtractor
    -> Tester
    <REJECTED> -> Junction
Tester
    BOOL_OP = OR
    TEST_CLAUSE = TEST @Value(_num_bands) = 1
    TEST_MODE = TEST
    PASSED -> RasterBandPropertyExtractor
    FAILED -> Junction_6
Note: Multiband Error
Junction_6
    -> Junction_7
Note: Unknown Error
Junction
    -> Junction_2

Bookmark: Check whether raster have proper interpretation
Note: Certain interpretations not supported
RasterBandPropertyExtractor
    -> Tester_2
    <REJECTED> -> Junction_3
Tester_2
    BOOL_OP = OR
    TEST_CLAUSE:
      TEST @Value(_band{0}.band_interpretation) BEGINS_WITH RED
      TEST @Value(_band{0}.band_interpretation) BEGINS_WITH GREEN8
      TEST @Value(_band{0}.band_interpretation) BEGINS_WITH BLUE
      TEST @Value(_band{0}.band_interpretation) BEGINS_WITH UINT
      TEST @Value(_band{0}.band_interpretation) BEGINS_WITH GRAY
    TEST_MODE = TEST
    PASSED -> AttributeCreator_10
    FAILED -> Junction_8
Note: Interpretation Error
Junction_8
    -> Junction_9
Note: Unknown Error
Junction_3
    -> Junction_2

Bookmark: Preliminary Processing
Note: Get index type (NDVI or SAVI) and / adjustment factor from parameters / and rename _band{0}.band_bit_depth / to _bitness
AttributeCreator_10
    ATTR_TABLE:
      SET_TO _index_type = $(INDEXTYPE)
      SET_TO _savi_adjustment = $(SAVIADJUSTMENT)
      SET_TO _bitness = @Evaluate(@pow(2,@Value(_band{0}.band_bit_depth))-1)
    -> RasterBandNodataRemover
Note: Remove nodata
RasterBandNodataRemover
    -> TestFilter_3
    <REJECTED> -> Junction_12
Note: Unknown Error
Junction_12
    -> Junction_2
Note: For SAVI, if no multiplier value provided, set it to 0.5
TestFilter_3
    DEFAULT_VALUE = SAVIadjustmentSet
    PASSED_TEST_GROUP_OUTPUT = FIRST
    TEST_LIST = BOOL_OP,OR,COMPOSITE_TEST,<Unused>,TEST_CLAUSE,"TEST _savi_adjustment ATTRIBUTE_IS_EMPTY """"",NoSAVIadjustmentValue
    NoSAVIadjustmentValue -> AttributeCreator
    SAVIadjustmentSet -> TestFilter_5
AttributeCreator
    ATTR_TABLE = SET_TO _savi_adjustment = 0.5
    -> TestFilter_5

Bookmark: Process Data According to Type
Note: Split into red and infrared
TestFilter_5
    DEFAULT_VALUE = infrared
    PASSED_TEST_GROUP_OUTPUT = FIRST
    TEST_LIST = BOOL_OP,OR,COMPOSITE_TEST,<Unused>,TEST_CLAUSE,"TEST @Value(_band_type) = red",red
    red -> TestFilter
    infrared -> TestFilter_2
Note: (NIR-RED) / NDVI=---------- / (NIR+RED) / https://en.wikipedia.org/wiki/Normalized_Difference_Vegetation_Index
TestFilter
    DEFAULT_VALUE = SAVI
    PASSED_TEST_GROUP_OUTPUT = FIRST
    TEST_LIST = BOOL_OP,OR,COMPOSITE_TEST,<Unused>,TEST_CLAUSE,"TEST @Value(_index_type) = NDVI",NDVI
    NDVI -> RasterExpressionEvaluator_2 [A]
    SAVI -> RasterExpressionEvaluator_4 [A]
Note: (1+L)(NIR-RED) / SAVI=---------------------------- / (NIR+RED+L) / L - canopy background adjustment factor (0.5 is good) / For SAVI, the pixel values are normalized. / https://en.wikipedia.org/wiki/Soil-Adjusted_Vegetation_Index
TestFilter_2
    DEFAULT_VALUE = SAVI
    PASSED_TEST_GROUP_OUTPUT = FIRST
    TEST_LIST = BOOL_OP,OR,COMPOSITE_TEST,<Unused>,TEST_CLAUSE,"TEST @Value(_index_type) = NDVI",NDVI
    NDVI -> RasterExpressionEvaluator_2 [B]
    SAVI -> RasterExpressionEvaluator_4 [B]

Bookmark: Calculate index
RasterExpressionEvaluator_2
    EXPRESSION_LIST = AUTO if(A[0]==0&&B[0]==0,-2,(B[0]-A[0])/(B[0]+A[0]))
    GROUP_BY = $(GROUP_BY)
    MODE = Two Rasters
    RESULT -> TestFilter_4
    <REJECTED> -> Junction_13
RasterExpressionEvaluator_4
    EXPRESSION_LIST = AUTO if(A[0]==0&&B[0]==0,-2,(1+@Value(B:_savi_adjustment))*((B[0]-A[0])/@Value(A:_bitness))/((B[0]+A[0])/@Value(A:_bitness)+@Value(B:_savi_adjustment)))
    GROUP_BY = $(GROUP_BY)
    MODE = Two Rasters
    RESULT -> TestFilter_4
    <REJECTED> -> Junction_13
Note: Unknown Error
Junction_13
    -> Junction_2

Bookmark: Index and Color Results
Note: Get the coloring type
TestFilter_4
    DEFAULT_VALUE = Do Not
    PASSED_TEST_GROUP_OUTPUT = FIRST
    TEST_LIST = BOOL_OP,OR,COMPOSITE_TEST,<Unused>,TEST_CLAUSE,"TEST $(COLORIZE) = Blue-Yellow-Green Palette",Blue-Yellow-Green Palette,BOOL_OP,OR,COMPOSITE_TEST,<Unused>,TEST_CLAUSE,"TEST $(COLORIZE) = Red-Yellow-Blue-Green Palette",Red-Yellow-Blue-Green Palette
    Blue-Yellow-Green Palette -> RasterExpressionEvaluator [A]
    Red-Yellow-Blue-Green Palette -> RasterExpressionEvaluator_3 [A]
    Do Not -> RasterBandNodataSetter_2
Note: Set nodata to -2 (because the range of possible values goes from -1 to 1)
RasterBandNodataSetter_2
    NODATA_VALUE = -2
    REPLACE_CELL_VALUES = No
    -> AttributeRemover

Bookmark: Make indexed rasters
Note: Define small ranges within the full index interval (from -1 to 1) and set integer values to them. / For example, 0 to 0.1 becomes 3, 0.1 to 0.2 becomes 4 etc.
RasterExpressionEvaluator
    EXPRESSION_LIST = UINT8 if(A[0]<-1,0,if(A[0]<=0,1,if(A[0]<0.033,2,if(A[0]<0.066,3,if(A[0]<0.1,4,if(A[0]<0.133,5,if(A[0]<0.166,6,if(A[0]<0.2,7,if(A[0]<0.25,8,if(A[0]<0.3,9,if(A[0]<0.35,10,if(A[0]<0.4,11,if(A[0]<0.45,12,if(A[0]<0.5,13,if(A[0]<0.6,14,if(A[0]<0.7,15,if(A[0]<0.8,16,if(A[0]<0.9,17,18))))))))))))))))))
    MODE = One Raster
    RESULT -> AttributeCreator_2
    <REJECTED> -> Junction_10
RasterExpressionEvaluator_3
    EXPRESSION_LIST = UINT8 if(A[0]<-1,0,if(A[0]<=-0.2,1,if(A[0]<-0.1,2,if(A[0]<0,3,if(A[0]<0.1,4,if(A[0]<0.2,5,if(A[0]<0.3,6,if(A[0]<0.4,7,if(A[0]<0.5,8,if(A[0]<0.6,9,if(A[0]<0.7,10,if(A[0]<0.8,11,if(A[0]<0.9,12,13)))))))))))))
    MODE = One Raster
    RESULT -> AttributeCreator_3
    <REJECTED> -> Junction_10
Note: Unknown Error
Junction_10
    -> Junction_2

Bookmark: Create Palettes
Note: Define RGB colors for each palette entry. The number of entries should be equal the number of defined ranges in the previous transformer plus one entry for nodata, which will be set 0.
AttributeCreator_2
    ATTR_TABLE:
      SET_TO _palette = RGB24
        0, 0,0,0
        1 0,148,255
        2 255,216,0
        3 196,186,164
        4 180,150,108
        5 164,130,76
        6 148,114,60
        7 124,158,44
        8 148,182,20
        9 116,170,4
        10 100,162,4
        11 84,150,4
        12 60,134,4
        13 37,120,5
        14 4,110,4
        15 4,90,4
        16 4,78,4
        17 4,64,4
        18 2,48,2
    -> RasterPaletteAdder
AttributeCreator_3
    ATTR_TABLE:
      SET_TO _palette = RGB24
        0, 0,0,0
        1 0,0,64
        2 255,0,0
        3 191,0,0
        4 127,0,0
        5 255,255,0
        6 191,191,0
        7 127,127,0
        8 0,255,255
        9 0,191,191
        10 0,127,127
        11 0,255,0
        12 0,191,0
        13 0,127,0
    -> RasterPaletteAdder_2

Bookmark: Add palette to raster
RasterPaletteAdder
    PALETTE_ATTR = _palette
    -> RasterBandNodataSetter
    <REJECTED> -> Junction_11
RasterPaletteAdder_2
    PALETTE_ATTR = _palette
    -> RasterBandNodataSetter
    <REJECTED> -> Junction_11
Note: Unknown Error
Junction_11
    -> Junction_2

Bookmark: Clean Up and Exit
Note: Set nodata to 0
RasterBandNodataSetter
    NODATA_VALUE = 0
    REPLACE_CELL_VALUES = No
    -> AttributeRemover
AttributeRemover
    LIST_ATTRS = _band{}
    REMOVE_ATTRS = _upper_right_y,_palette,_bitness,_num_rows,_max_y,_num_bands,_num_columns,_spacing_x,_min_x,_savi_adjustment,_band_type,_lower_right_x,_rotation_x,_lower_right_y,_upper_left_y,_lower_left_y,_min_y,_upper_right_x,_cell_origin_y,_spacing_y,_cell_origin_x,_index_type,_origin_y,_max_x,_origin_x,_rotation_y,_lower_left_x,_upper_left_x
    -> AttributeCreator_9
AttributeCreator_9
    ATTR_TABLE = SET_TO fme_basename = $(INDEXTYPE)
    -> Output (output)
Output (output)

Bookmark: ERRORS: Add rejection message and output through Rejected port
Note: Interpretation Error
Junction_9
    -> AttributeCreator_8
AttributeCreator_8
    ATTR_TABLE = SET_TO _rejection_message = The raster has invalid interpetation (not one of the unsigned integer 8 or 16 bit such as UINT8, GRAY, RED, GREEN, BLUE, ALPHA)
    -> <Rejected> (output)
Note: Multiband Error
Junction_7
    -> AttributeCreator_7
AttributeCreator_7
    ATTR_TABLE = SET_TO _rejection_message = The raster has more than one band
    -> <Rejected> (output)
Note: Unknown Error
Junction_2
    -> AttributeCreator_11
AttributeCreator_11
    ATTR_TABLE = SET_TO _rejection_message = The transformer experienced an unknown error
    -> <Rejected> (output)
Note: Bad Geometry Error
Junction_5
    -> AttributeCreator_6
AttributeCreator_6
    ATTR_TABLE = SET_TO _rejection_message = The feature is not a raster
    -> <Rejected> (output)
<Rejected> (output)

FME custom transformer EarthCacheConnector
Overview
Description
Connects to the SkyWatch EarthCache™ platform enabling users to search for previously collected Earth observation data (archive) or request future Earth observation data be collected (tasking). Once data is processed, after a few minutes for archive data, after the collection for future data, the connector allows for the subsequent download and ingestion of results into FME.
Users must have a valid EarthCache account. To request an EarthCache API key, simply head over to the SkyWatch website. To learn more about which datasets are available through EarthCache, visit SkyWatch’s data partners page.
Details
Features with geometry that defines an area of interest enter the SkyWatchConnector. The transformer parameters define an EarthCache pipeline to create. Data is then validated and various requests are made to the SkyWatch EarthCache REST API. Finally image URLs are fed into a FeatureReader and exit the output port.
When data is available, each pipeline will return the best available result per interval based on your specified attributes. For future pipelines, results will be returned once the interval is completed, unless otherwise specified. 
All EarthCache accounts offer access to low resolution, open data, such as Sentinel-2 or Landsat-8. In order to access medium or high resolution data, users must upgrade their account to a Build or Scale tier within their EarthCache dashboard or simply by contacting sales@skywatch.com. There is no cost to create an account, upgrade an account, and access open data. Medium (3-5m resolution) and high resolution data (from 80cm to 50 cm resolution) are available on a pay-per-use basis, starting at 0.1km2.
Input Ports
Features entering the input port are expected to be polygons with a latitude/longitude coordinate system. These define an area of interest for the SkyWatch imagery search.
Output Ports
Images from pipeline results exit the output port. Any rejected features, including search results for dates that contain no results that meet the search criteria, exit the rejected port.
Due to the large number of metadata attributes that accompany pipeline results, most of these are not exposed by default, but do exist on the features as unexposed attributes.
Parameters
Pipeline Name: The name of the search or "pipeline".
API Key: Your SkyWatch EarthCache API key.
Search Interval: Search frequency between start and end dates.
Start Date: Date the search starts.
End Date: Date the search ends.
Minimum Coverage Percentage: Minimum usable data percentage per image. Below this threshold, images will be rejected.
Image Type: The type of imagery product you wish to search.
Notes
If you attempt to create a pipeline with the same name as an existing pipeline, FME will simply return the results of the existing pipeline with the same name.

Parameters:
- pipeline_name =   # Pipeline Name
- api_key =   # API Key
- interval =   # Search Interval
- start_date =   # "{}" Start Date
- end_date =   # "{}" End Date
- min_aoi_coverage_percentage = 80   # Minimum Coverage Percentage
- output_id = a8fc3dde-a3e8-11e7-9793-ae4260ee3b4b

Input (input)
    -> ParameterFetcher
ParameterFetcher
    ATTR_LIST = pipeline_name $(pipeline_name) api_key $(api_key) end_date $(end_date) interval $(interval) min_aoi_coverage_percentage $(min_aoi_coverage_percentage) start_date $(start_date) output_id $(output_id)
    -> DateTimeConverter
GeometryExtractor
    ATTR = aoi
    JSON_MAX_DIGITS = 7
    KIND_LONG = GeoJSON
    REMOVE_GEOMETRY = Yes
    -> PythonCaller
    <REJECTED> -> <Rejected> (output)
Output (output)

Bookmark: Validate Dates
DateTimeConverter
    DATETIME_ATTR = start_date end_date
    OUT_FORMAT = %Y-%m-%d
    PASSTHROUGH = NO
    REPAIR_INPUT = YES
    -> DateTimeCalculator
    <REJECTED> -> <Rejected> (output)
DateTimeCalculator
    MODE = DATETIMECALC_3_CALCULATE_INTERVAL
    OPERATION_PARAMETERS = START_DATETIME]@Value(start_date)]END_DATETIME]@Value(end_date)]RESULT_TYPE]SECONDS]RESULT_INTERVAL]_result_interval]FME_CONTROLLER_QUERY_FILE]transformers/dependencies/datetimecalculator/DATETIMECALC_3_CALCULATE_INTERVAL.fme
    -> Tester
Tester
    BOOL_OP = OR
    TEST_CLAUSE = TEST @Value(_result_interval) >= 0
    TEST_MODE = TEST
    PASSED -> GeometryExtractor
    FAILED -> AttributeCreator

Bookmark: All API Requests
PythonCaller
    NEW_ATTRIBUTES = results
    PYTHONSOURCE:
      import requests
      import json
      import time
      import fmeobjects

      #Helper functions.
      def checkPipelineExists(**kwargs):
      	#Get existing pipelines, names and ids in separate lists.
      	url = kwargs["pipeline_url"]
      	print("Checking SkyWatch pipelines...")
      	r = requests.get(url,headers=kwargs["headers"])
      	print("GET " + str(r.request.url) + '\n' + str(r.request.headers))
      	data = r.json()["data"]
      	names = []
      	ids = []
      	for x in data:
      		names.append(x["name"])
      		ids.append(x["id"])
      	#Check the user-typed name against the list of existing names. Set the "exists" key accordingly.
      	if kwargs["pipeline_name"] in names:
      		print("A pipeline with the name \"" + kwargs["pipeline_name"] + "\" already exists.")
      		kwargs["exists"] = True
      		kwargs["pipeline_id"] = ids[names.index(kwargs["pipeline_name"])]
      		print("The id for \"" + kwargs["pipeline_name"] + "\" is" + kwargs["pipeline_id"] + ".")
      	else:
      		kwargs["exists"] = False
      	return kwargs

      def createPipeline(**kwargs):
      	#Create a new pipeline.
      	url = kwargs["pipeline_url"]
      	print("Creating new SkyWatch pipeline named \"" + kwargs["pipeline_name"] + "\".")
      	r = requests.post(url,json=kwargs["body"],headers=kwargs["headers"])
      	print("POST " + str(r.request.url) + '\n' + str(r.request.headers) + '\n' + str(r.request.body))
      	print("Response: " + r.text)
      	status = r.json()["data"]["status"]
      	pipeline_id = r.json()["data"]["id"]
      	kwargs["pipeline_id"] = pipeline_id
      	kwargs["status"] = status
      	return kwargs

      def checkPipelineStatus(**kwargs):
      	url = kwargs["pipeline_url"] + kwargs["pipeline_id"]
      	#We don't want to go further until the status is 'complete', so keep checking.
      	while kwargs["status"] != 'complete':
      		print("Checking pipeline status...")
      		r = requests.get(url,headers=kwargs["headers"])
      		print("GET " + str(r.request.url) + '\n' + str(r.request.headers))
      		kwargs["status"] = r.json()["data"]["status"]
      		if kwargs["status"] != 'complete':
      			print("Waiting for results...")
      			time.sleep(10)
      	print("Pipeline complete.")
      	return kwargs

      def getResults(**kwargs):
      	#Dump the results. These will go back to FME for parsing.
      	url = kwargs["pipeline_url"] + kwargs["pipeline_id"] + '/interval_results'
      	if kwargs["status"] == 'complete':
      		print("Retrieving pipeline results...")
      		r = requests.get(url,headers=kwargs["headers"])
      		print("GET " + str(r.request.url) + '\n' + str(r.request.headers))
      		print(r.text)
      	return r.text

      #Start processing features here.
      class FeatureProcessor(object):

      	def __init__(self):
      		#Data dictionary for use in SkyWatch API requests.
      		self.pipeline_data = {
      								"pipeline_name": None,
      								"interval": None,
      								"start_date": None,
      								"end_date": None,
      								"output_id": None,
      								"aoi": None,
      								"min_aoi_coverage_percentage": None,
      								"pipeline_url": None,
      								"pipeline_id": None,
      								"status": None,
      								"exists": None,
      								"pipeline_url": "https://api.skywatch.co/earthcache/pipelines/",
      								"api_key": None,
      								"headers": None,
      								"body": None
      								}

      	def input(self,feature):
      		#Build the data dictionary.
      		for key in self.pipeline_data:
      			if feature.getAttribute(key):
      				self.pipeline_data[key] = feature.getAttribute(key)
      		self.pipeline_data["headers"] = {"x-api-key": self.pipeline_data["api_key"]}
      		self.pipeline_data["body"] = {
      			"name": self.pipeline_data["pipeline_name"],
      			"interval": str(self.pipeline_data["interval"]) + 'd',
      			"start_date": self.pipeline_data["start_date"],
      			"end_date": self.pipeline_data["end_date"],
      			"min_aoi_coverage_percentage": int(self.pipeline_data["min_aoi_coverage_percentage"]),
      			"output": {
      			"id": self.pipeline_data["output_id"],
      			"format": "geotiff",
      			"mosaic": "off"
      			},
      			"aoi": json.loads(self.pipeline_data["aoi"]),
      			"max_cost": 0,
      			"result_delivery": {
      			"max_latency": "0d",
      			"priorities": [
      			"highest_resolution",
      			"latest",
      			"lowest_cost"
      			]
      			},
      			"resolution_low": 30,
      			"resolution_high": 10,
      			"tags": []
      			}
      		print("User data: " + str(self.pipeline_data))
      		#Begin API requests
      		self.pipeline_data = checkPipelineExists(**self.pipeline_data)
      		#If the pipeline exists, just get the results. Else create the new pipeline first.
      		if self.pipeline_data["exists"]:
      			self.pipeline_data = checkPipelineStatus(**self.pipeline_data)
      			feature.setAttribute("results",getResults(**self.pipeline_data))
      		else:
      			self.pipeline_data = createPipeline(**self.pipeline_data)
      			self.pipeline_data = checkPipelineStatus(**self.pipeline_data)
      			feature.setAttribute("results",getResults(**self.pipeline_data))
      		self.pyoutput(feature)

      	def close(self):
      		pass
    PYTHONSYMBOL = FeatureProcessor
    -> JSONFragmenter

Bookmark: Parse Down to Results
JSONFragmenter
    EXPLODE_FORMAT = JSON
    EXTRACT_ATTR = Yes
    JSON_ATTR = results
    JSON_QUERY = json["data"][*]
    READ_FROM_FILE = NO
    RECURSIVE = Yes
    REJECT_EMPTY_LISTS = YES
    FRAGMENTS -> JSONFragmenter_2
    <REJECTED> -> <Rejected> (output)
JSONFragmenter_2
    EXPLODE_FORMAT = JSON
    EXTRACT_ATTR = Yes
    JSON_ATTR = results
    JSON_QUERY = json["results"][*]
    NEW_ATTRIBUTES = analytics_url
    READ_FROM_FILE = NO
    RECURSIVE = Yes
    REJECT_EMPTY_LISTS = YES
    FRAGMENTS -> FeatureReader [INITIATOR]
    <REJECTED> -> Sampler

Bookmark: Read result URLs
FeatureReader
    ATTR_ACCUM_MODE = Merge Initiator and Result
    ATTR_CONFLICT_RES = Use Result
    CACHE_TIMEOUT_HRS = 24
    COMBINE_GEOM = Use Result
    DATASET = @Value(analytics_url)
    FORMAT = GEOTIFF
    GEOTIFF_APPLY_GCPS = NO
    GEOTIFF_FEATURE_TYPE_NAME = FILE_NAME_AND_SUBDATASET_NAME
    GEOTIFF_IGNORE_RASTER_TYPE_KEY = No
    GEOTIFF_PREFER_FILE_CS_UNITS = Yes
    GEOTIFF_READER_META_ATTRIBUTES = fme_dataset fme_basename
    GEOTIFF_READ_OFFSETS_IN_CS_UNITS = No
    GEOTIFF_USE_SEARCH_ENVELOPE = NO
    INTERACT = <No Spatial Filter>
    OUTPUT_FEATURES_DISPLAY = Data Features
    <OTHER> -> Output (output)
    <REJECTED> -> <Rejected> (output)

Bookmark: No Results
Sampler
    RATE = 1
    SAMPLE_MODE = No
    SAMPLE_TYPE_LONG = Every Nth Feature
    SAMPLED -> AttributeCreator_2
AttributeCreator_2
    ATTR_TABLE = SET_TO fme_rejection_code = No results.
    -> <Rejected> (output)

Bookmark: Invalid dates
AttributeCreator
    ATTR_TABLE = SET_TO fme_rejection_code = Invalid start and end dates.
    -> <Rejected> (output)

Bookmark: Rejected
<Rejected> (output)
